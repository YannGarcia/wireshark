-- ^-^-^-^-^-^-^-^-^-^-^-^-^-^-^-^-^-^-^-^-^-^-^-^-^-^-^-^-
-- 
-- module: REGION
-- TS 19091 Oct 2015 v0909
-- 
-- ^-^-^-^-^-^-^-^-^-^-^-^-^-^-^-^-^-^-^-^-^-^-^-^-^-^-^-^-

REGION  { 	iso (1) standard (0) signalizedIntersection (19091) profilec(2) region (1) version (1) }

DEFINITIONS AUTOMATIC TAGS::= BEGIN 

IMPORTS
addGrpC, REG-EXT-ID-AND-TYPE	FROM DSRC
ConnectionManeuverAssist-addGrpC, ConnectionTrajectory-addGrpC, IntersectionState-addGrpC, Control-addGrpC,  Position3D-addGrpC, RestrictionUserType-addGrpC,
SignalStatusPackage-addGrpC, MapData-addGrpC  FROM AddGrpC {iso (1) standard (0) signalizedIntersection (19091) profilec(2) addgrpc (0) version (1)};

Reg-AdvisorySpeed					REG-EXT-ID-AND-TYPE ::= { ... }

Reg-ComputedLane					REG-EXT-ID-AND-TYPE ::= { ... }

Reg-ConnectionManeuverAssist	REG-EXT-ID-AND-TYPE ::= { 
	{ConnectionManeuverAssist-addGrpC	IDENTIFIED BY addGrpC} ,
	... 
}

Reg-GenericLane           REG-EXT-ID-AND-TYPE ::= {
	{ConnectionTrajectory-addGrpC	IDENTIFIED BY addGrpC} ,
	... 
}

Reg-IntersectionGeometry  REG-EXT-ID-AND-TYPE ::= { ...  }

Reg-IntersectionState     REG-EXT-ID-AND-TYPE ::= {
	{IntersectionState-addGrpC IDENTIFIED BY addGrpC} ,
	...
}

Reg-LaneAttributes        		REG-EXT-ID-AND-TYPE ::= { ...  }

Reg-LaneDataAttribute     	REG-EXT-ID-AND-TYPE ::= { ... }

Reg-MapData								REG-EXT-ID-AND-TYPE ::= { 
  	 {MapData-addGrpC  IDENTIFIED BY addGrpC},
   	... 
}

Reg-MovementEvent         	REG-EXT-ID-AND-TYPE ::= { ... }

Reg-MovementState         	REG-EXT-ID-AND-TYPE ::= { ...  }

Reg-NodeAttributeSetLL    	REG-EXT-ID-AND-TYPE ::= { ...  }

Reg-NodeAttributeSetXY    	REG-EXT-ID-AND-TYPE ::= {
	{Control-addGrpC	IDENTIFIED BY addGrpC} ,
	 ...
}

Reg-NodeOffsetPointLL     	REG-EXT-ID-AND-TYPE ::= { ...  }

Reg-NodeOffsetPointXY     	REG-EXT-ID-AND-TYPE ::= { ... }

Reg-Position3D            		REG-EXT-ID-AND-TYPE ::= {
	{Position3D-addGrpC IDENTIFIED BY addGrpC} ,
	...
}

Reg-RequestorDescription  	REG-EXT-ID-AND-TYPE ::= { ...  }

Reg-RequestorType         	REG-EXT-ID-AND-TYPE ::= { ...  }

Reg-RestrictionUserType   	REG-EXT-ID-AND-TYPE ::= { 
	{RestrictionUserType-addGrpC IDENTIFIED BY addGrpC} ,
	...
}

Reg-RoadSegment						REG-EXT-ID-AND-TYPE ::= { ...  }

Reg-SignalControlZone				REG-EXT-ID-AND-TYPE ::= { ...  }

Reg-SignalRequest					REG-EXT-ID-AND-TYPE ::= { ...  }

Reg-SignalRequestMessage			REG-EXT-ID-AND-TYPE ::= { ... }

Reg-SignalRequestPackage			REG-EXT-ID-AND-TYPE ::= { ...  }

Reg-SignalStatus					REG-EXT-ID-AND-TYPE ::= { ...  }

Reg-SignalStatusMessage				REG-EXT-ID-AND-TYPE ::= { ... }

Reg-SignalStatusPackage   	REG-EXT-ID-AND-TYPE ::= { 
	{ SignalStatusPackage-addGrpC IDENTIFIED BY addGrpC} ,
	...
}

Reg-SPAT                            REG-EXT-ID-AND-TYPE ::= { ... }

END
